;updated on 29-3-19
(defun c:Summ()

 (defun *error* (msg) (vl-cmdf "UNDO" "b") (princ msg))
 (vl-cmdf "UNDO" "m")
 (setvar "cmdecho" 0)
;;; (setq tot_len 0)
 (vl-load-com)
 (chkpwd)
 (if pwd
  (progn
 (setq smbool t)
 (setq sumlst nil)
 (prompt "\nSelect all objects to count: ")
 (setq ss (ssget))
 (setq sobj (ssname ss 0))
 (setq sdata (entget sobj))
 (setq sla (cdr (assoc 8 sdata)))
;;; (setq la(getvar "clayer"))
;;; (command "layer" "m" "calc" "")
 (setq n 0)
 (setq detailsbool nil)
 (setq rbool nil)
 (setq writebool nil)
 (setq laylist nil)
 (setq gvn "")
 (while (< n (sslength ss))
  (setq nobj (ssname ss n))
  (setq objname (cdr (assoc 0 (entget nobj))))
  (setq objlay (cdr (assoc 8 (entget nobj))))
  (if (or (= objname "LINE") (= objname "ARC") (= objname "POLYLINE") (= objname "LWPOLYLINE"))
   (progn (setq obj (vlax-ename->vla-object nobj))
          (if laylist
           (progn (setq lbool nil)
                  (foreach item laylist
                   (if (wcmatch item objlay)
                    (setq lbool t)
                   )
                  )
                  (if (= lbool nil)
                   (setq laylist (cons objlay laylist))
                  )
           )
           (setq laylist (cons objlay laylist))
          )
   )
  )
  (setq n (+ n 1))
 )
;;; (xplodepolylines)
 (setq tempset (ssadd))
 (duplicates)
 (foreach layitem laylist
  (setq lset (ssadd))
  (setq lcount 0)
  (setq tot_len 0)
  (setq len_lst nil)
  (repeat (sslength tempset)
   (setq lset (ssadd (ssname tempset lcount) lset))
   (setq lcount (+ lcount 1))
  )
  (setq n (- (sslength lset) 1))
  (while (and(> (sslength lset) 0)(>= n 0))
   (setq en (ssname lset n))
   (setq ed (entget en))
   (setq elay (cdr (assoc 8 ed)))
   (setq e_type (cdr (assoc '0 ed)))

   (getprofileonly)
;;;   (if (or (= pr "") (= pr nil))
;;;         (progn (alert (strcat "missing profile   for layer " layitem ".Update & rerun ")) (exit))
;;;         
;;;        )
;;;   (if (= pr nil)
;;;    (setq pr "UNKNOWN")
;;;    )
   (if (/= pr nil)
    (progn
   (cond ((= e_type "LINE") (add_lines))
         ((= e_type "ARC") (add_arcs))
         ((= e_type "POLYLINE") (add_poly))
         ((= e_type "LWPOLYLINE") (add_poly))
         ((and (/= e_type "LINE") (/= e_type "ARC") (/= e_type "POLYLINE") (/= e_type "LWPOLYLINE"))
          (ssdel en lset)
         )
   )
   )
    
         ;(progn (alert (strcat "missing profile   for layer" layitem ".Update & rerun ")) (exit))
         
        
    )
   (setq n (- n 1))
  )
   (if sumlst 
  (setq sumlst (vl-sort sumlst (function (lambda (e1 e2) (eq (car e1) (car e2))))))
    )
 )
 (summaryfileNew)
;;; (princ)
 (setvar "cmdecho" 1)
 (print "Success")
 (princ)
 )
  )
 
 )

(defun c:Summary()
 (defun *error* (msg) (vl-cmdf "UNDO" "b") (princ msg))
 (vl-cmdf "UNDO" "m")
 (setvar "cmdecho" 0)
;;; (setq tot_len 0)
 (vl-load-com)
 (chkpwd)
 (if pwd
  (progn
 (setq smbool t)
 (setq sumlst nil)
 (prompt "\nSelect all objects to count: ")
 (setq ss (ssget))
 (setq sobj (ssname ss 0))
 (setq sdata (entget sobj))
 (setq sla (cdr (assoc 8 sdata)))
;;; (setq la(getvar "clayer"))
;;; (command "layer" "m" "calc" "")
 (setq n 0)
 (setq detailsbool nil)
 (setq rbool nil)
 (setq writebool nil)
 (setq laylist nil)
 (setq gvn "")
 (while (< n (sslength ss))
  (setq nobj (ssname ss n))
  (setq objname (cdr (assoc 0 (entget nobj))))
  (setq objlay (cdr (assoc 8 (entget nobj))))
  (if (or (= objname "LINE") (= objname "ARC") (= objname "POLYLINE") (= objname "LWPOLYLINE"))
   (progn (setq obj (vlax-ename->vla-object nobj))
          (if laylist
           (progn (setq lbool nil)
                  (foreach item laylist
                   (if (wcmatch item objlay)
                    (setq lbool t)
                   )
                  )
                  (if (= lbool nil)
                   (setq laylist (cons objlay laylist))
                  )
           )
           (setq laylist (cons objlay laylist))
          )
   )
  )
  (setq n (+ n 1))
 )
;;; (xplodepolylines)
 (setq tempset (ssadd))
 (duplicates)
 (foreach layitem laylist
  (setq lset (ssadd))
  (setq lcount 0)
  (setq tot_len 0)
  (setq len_lst nil)
  (repeat (sslength tempset)
   (setq lset (ssadd (ssname tempset lcount) lset))
   (setq lcount (+ lcount 1))
  )
  (setq n (- (sslength lset) 1))
  (while (and(> (sslength lset) 0)(>= n 0))
   (setq en (ssname lset n))
   (setq ed (entget en))
   (setq elay (cdr (assoc 8 ed)))
   (setq e_type (cdr (assoc '0 ed)))
   (getprofile)
;;;   (if (or (= pr "") (= pr nil))
;;;         (progn (alert (strcat "missing profile   for layer " layitem ".Update & rerun ")) (exit))
;;;         
;;;        )
   (if (/= pr nil)
    (progn
   (cond ((= e_type "LINE") (add_lines))
         ((= e_type "ARC") (add_arcs))
         ((= e_type "POLYLINE") (add_poly))
         ((= e_type "LWPOLYLINE") (add_poly))
         ((and (/= e_type "LINE") (/= e_type "ARC") (/= e_type "POLYLINE") (/= e_type "LWPOLYLINE"))
          (ssdel en lset)
         )
   )
   )
    
         ;(progn (alert (strcat "missing profile   for layer" layitem ".Update & rerun ")) (exit))
         
        
    )
   (setq n (- n 1))
  )
   (if sumlst 
  (setq sumlst (vl-sort sumlst (function (lambda (e1 e2) (eq (car e1) (car e2))))))
    )
 )
 (summaryfileOnly)
;;; (princ)
 (setvar "cmdecho" 1)
 (print "Success")
 (princ)
 )
  )
 )
(defun C:SM ()
 (defun *error* (msg) (vl-cmdf "UNDO" "b") (princ msg))
 (vl-cmdf "UNDO" "m")
 (setvar "cmdecho" 0)
;;; (setq tot_len 0)
 (vl-load-com)
  (chkpwd)
(if pwd
 (progn
 
 (setq smbool t)
 (setq sumlst nil)
 (prompt "\nSelect all objects to count: ")
 (setq ss (ssget))
 (setq sobj (ssname ss 0))
 (setq sdata (entget sobj))
 (setq sla (cdr (assoc 8 sdata)))
;;; (setq la(getvar "clayer"))
;;; (command "layer" "m" "calc" "")
 (setq n 0)
 (setq detailsbool nil)
 (setq rbool nil)
 (setq writebool nil)
 (setq laylist nil)
 (setq gvn "")
 (while (< n (sslength ss))
  (setq nobj (ssname ss n))
  (setq objname (cdr (assoc 0 (entget nobj))))
  (setq objlay (cdr (assoc 8 (entget nobj))))
  (if (or (= objname "LINE") (= objname "ARC") (= objname "POLYLINE") (= objname "LWPOLYLINE"))
   (progn (setq obj (vlax-ename->vla-object nobj))
          (if laylist
           (progn (setq lbool nil)
                  (foreach item laylist
                   (if (wcmatch item objlay)
                    (setq lbool t)
                   )
                  )
                  (if (= lbool nil)
                   (setq laylist (cons objlay laylist))
                  )
           )
           (setq laylist (cons objlay laylist))
          )
   )
  )
  (setq n (+ n 1))
 )
;;; (xplodepolylines)
 (setq tempset (ssadd))
 (duplicates)
 (foreach layitem laylist
  (setq lset (ssadd))
  (setq lcount 0)
  (setq tot_len 0)
  (setq len_lst nil)
  (repeat (sslength tempset)
   (setq lset (ssadd (ssname tempset lcount) lset))
   (setq lcount (+ lcount 1))
  )
  (setq n (- (sslength lset) 1))
  (while (and(> (sslength lset) 0)(>= n 0))
   (setq en (ssname lset n))
   (setq ed (entget en))
   (setq elay (cdr (assoc 8 ed)))
   (setq e_type (cdr (assoc '0 ed)))
   (getprofile)
;;;   (if (or (= pr "") (= pr nil))
;;;         (progn (alert (strcat "missing profile   for layer " layitem ".Update & rerun ")) (exit))
;;;         
;;;        )
   (if (/= pr nil)
    (progn
   (cond ((= e_type "LINE") (add_lines))
         ((= e_type "ARC") (add_arcs))
         ((= e_type "POLYLINE") (add_poly))
         ((= e_type "LWPOLYLINE") (add_poly))
         ((and (/= e_type "LINE") (/= e_type "ARC") (/= e_type "POLYLINE") (/= e_type "LWPOLYLINE"))
          (ssdel en lset)
         )
   )
   )
    
;;;         (progn (alert (strcat "missing profile   for layer" layitem ".Update & rerun ")) (exit))
         
        
    )
   (setq n (- n 1))
  )
   (if sumlst 
  (setq sumlst (vl-sort sumlst (function (lambda (e1 e2) (eq (car e1) (car e2))))))
    )
 )
 (summaryfile)
;;; (princ)
 (setvar "cmdecho" 1)
 (print "Success")
 (princ)
 )
 )
)
;_
(defun chkpwd()
 (setq pwd nil) 
 (setq file (findfile "MTO.asc"))
 (if file
  (progn
   (setq fs (open file "r"))
   (while (and (setq ln (read-line fs)) (/= "EOF" ln) (/= "" ln))    
    (if (= ln "PTOTEK1")
    (progn
      (setq pwd t)
     )
    )
   )
   
   (close fs)
   )
  )
 
 )
;_
(defun getprofileonly ()
 (setq dwgpath (getvar "DWGPREFIX"))
 (setq adfilename (strcat dwgpath "MATERIAL-TAKEOFF.csv"))
 (setq file (findfile adfilename))
 (if file
  (progn
   (setq fcount 0)
   (setq fs (open file "r"))
   (setq data nil)
   (setq details nil)
   (while (and (setq ln (read-line fs)) (/= "EOF" ln) (/= "" ln))
    (setq fcount (+ fcount 1))
    (setq data (cons (str2lst ln "," nil) data))
   )
   (close fs)
   (setq data (reverse data))
   (if data
    (progn
     (setq gvn " ")
     (setq wt " ")
     (Setq pr nil)
     (foreach item data
      (setq layername   (car item)
            profilename (cadr item)
            totallength (caddr item)
;;;                col         (atoi (last item))
            galv        (nth 4 item)
            col         (nth 5 item)
      )
      (setq tot_wt 0)
            
      (if (wcmatch layitem layername)
       (progn
;;;        (setq gvn galv)
        (setq pr profilename)
;;;        (setq wt (getWt profilename))
;;;        (if (or (= wt "") (= wt nil))
;;;         (progn (alert (strcat "missing data  wt/m  for profile:" pr ".Update & rerun ")) (exit))
;;;         (setq wt (atof wt))
;;;        )
;;;        (if (or (= pr "") (= pr nil))
;;;         (progn (alert (strcat "missing profile   for layer" layitem ".Update & rerun ")) (exit))
;;;         
;;;        )
       )
      )
     )
    )
   )
  )
 )
)

 ;_
(defun getprofile ()
 (setq dwgpath (getvar "DWGPREFIX"))
 (setq adfilename (strcat dwgpath "MATERIAL-TAKEOFF.csv"))
 (setq file (findfile adfilename))
 (if file
  (progn
   (setq fcount 0)
   (setq fs (open file "r"))
   (setq data nil)
   (setq details nil)
   (while (and (setq ln (read-line fs)) (/= "EOF" ln) (/= "" ln))
    (setq fcount (+ fcount 1))
    (setq data (cons (str2lst ln "," nil) data))
   )
   (close fs)
   (setq data (reverse data))
   (if data
    (progn
     (setq gvn "")
     (setq wt nil)
     (Setq pr nil)
     (foreach item data
      (setq layername   (car item)
            profilename (cadr item)
            totallength (caddr item)
;;;                col         (atoi (last item))
            galv        (nth 4 item)
            col         (nth 5 item)
      )
      (setq tot_wt 0)
            
      (if (wcmatch layitem layername)
       (progn
        (setq gvn galv)
        (setq pr profilename)
        (setq wt (getWt profilename))
        (if (or (= wt "") (= wt nil))
         (progn (alert (strcat "missing data  wt/m  for profile:" pr ".Update & rerun ")) (exit))
         (setq wt (atof wt))
        )
        (if (or (= pr "") (= pr nil))
         (progn (alert (strcat "missing profile   for layer" layitem ".Update & rerun ")) (exit))
         
        )
       )
      )
     )
    )
   )
  )
 )
)
;_
(defun writeSummary2csv ()
 (setq dwgpath (getvar "DWGPREFIX"))
 (setq adfilename (strcat dwgpath "MATERIAL-TAKEOFF_Summary.csv")) ;(setq file filename )
 (setq file (findfile adfilename))
;;; (if(= file nil)
;;;  	(setq file (getfiled adfilename "" "csv" 1))
;;;  )
;;; (if file
;;;  (progn
   (setq file (open adfilename "w"))
;;;         (write-line "TAKE DETAILED" file)
;;;         (write-line "LAYER,PROFILE,LENGTH,WT/M,GALVANIZED" file)
;;;         (foreach item sumlst (setq strdetail (lst2222str item ",")) (write-line strdetail file))
         (write-line "SUMMARY" file)
         (write-line "LAYER,PROFILE,LENGTH,QTY,TOTALLENGTH,TOTALWT,GALVANIZED" file)
         (foreach item flist (setq strdetail (lst22222str item ",")) (write-line strdetail file))
         (close file)
;;;  )
;;;  (progn
;;;;;;   (alert (strcat  adfilename "file not found"))
;;;;;;         (print (strcat adfilename "file not found"))
;;;;;;         (princ)
;;;  )
;;; )
)
;_
(defun writeSummary2csvOld ()
 (setq dwgpath (getvar "DWGPREFIX"))
 (setq adfilename (strcat dwgpath "MATERIAL-TAKEOFF.csv")) ;(setq file filename )
 (setq file (findfile adfilename))
 (if file
  (progn (setq file (open adfilename "a"))
;;;         (write-line "TAKE DETAILED" file)
;;;         (write-line "LAYER,PROFILE,LENGTH,WT/M,GALVANIZED" file)
;;;         (foreach item sumlst (setq strdetail (lst2222str item ",")) (write-line strdetail file))
         (write-line "SUMMARY" file)
         (write-line "LAYER,PROFILE,LENGTH,QTY,TOTALLENGTH,TOTALWT,GALVANIZED" file)
         (foreach item flist (setq strdetail (lst22222str item ",")) (write-line strdetail file))
         (close file)
  )
  (progn
;;;   (alert (strcat  adfilename "file not found"))
         (print (strcat adfilename "file not found"))
         (princ)
  )
 )
)
;_
(defun write2csvNew ()
 (setq dwgpath (getvar "DWGPREFIX"))
 (setq dwgname(getvar "DWGNAME"))
 ;(setq adfilename (strcat dwgpath "MATERIAL-TAKEOFF_Details.csv")) ;(setq file filename )
 (setq adfilename (strcat dwgpath dwgname "-MTO-DETAILS.csv"))
 (setq file (findfile adfilename))
;;; (if file
;;;  (progn
   (setq file (open adfilename "w"))
         (write-line "TAKEOFF DETAILS" file)
         ;(write-line "LAYER,PROFILE,LENGTH,WT/M,GALVANIZED" file)
 (write-line "LAYER,PROFILE,LENGTH" file)

 (foreach item sumlst (setq strdetail (lst2222strNew item ",")) (write-line strdetail file))
 (close file)

 (setq adfilename (strcat dwgpath dwgname "-MTO-SUMMARY.csv"))
 (setq file (findfile adfilename))
 (setq file (open adfilename "w"))
 
         (write-line "SUMMARY" file)
        ; (write-line "LAYER,PROFILE,LENGTH,QTY,TOTALLENGTH,TOTALWT,GALVANIZED" file)
 (write-line "LAYER,PROFILE,LENGTH,QTY,TOTALLENGTH" file)
         (foreach item flist (setq strdetail (lst22222strNew item ",")) (write-line strdetail file))
         (close file)
;;;  )
;;;  (progn
;;;;;;   (alert (strcat  adfilename "file not found"))
;;;         (print (strcat adfilename "file not found"))
;;;         (princ)
;;;  )
;;; )
)
;_
(defun write2csv ()
 (setq dwgpath (getvar "DWGPREFIX"))
 (setq adfilename (strcat dwgpath "MATERIAL-TAKEOFF_Details.csv")) ;(setq file filename )
 (setq file (findfile adfilename))
;;; (if file
;;;  (progn
   (setq file (open adfilename "w"))
         (write-line "TAKEOFF DETAILS" file)
         (write-line "LAYER,PROFILE,LENGTH,WT/M,GALVANIZED" file)

 (foreach item sumlst (setq strdetail (lst2222str item ",")) (write-line strdetail file))
         (write-line "SUMMARY" file)
         (write-line "LAYER,PROFILE,LENGTH,QTY,TOTALLENGTH,TOTALWT,GALVANIZED" file)
         (foreach item flist (setq strdetail (lst22222str item ",")) (write-line strdetail file))
         (close file)
;;;  )
;;;  (progn
;;;;;;   (alert (strcat  adfilename "file not found"))
;;;         (print (strcat adfilename "file not found"))
;;;         (princ)
;;;  )
;;; )
)


 ;_
(defun write2csvold ()
 (setq dwgpath (getvar "DWGPREFIX"))
 (setq adfilename (strcat dwgpath "MATERIAL-TAKEOFF.csv")) ;(setq file filename )
 (setq file (findfile adfilename))
 (if file
  (progn (setq file (open adfilename "a"))
         (write-line "TAKE DETAILED" file)
         (write-line "LAYER,PROFILE,LENGTH,WT/M,GALVANIZED" file)
         (foreach item sumlst (setq strdetail (lst2222str item ",")) (write-line strdetail file))
         (write-line "SUMMARY" file)
         (write-line "LAYER,PROFILE,LENGTH,QTY,TOTALLENGTH,TOTALWT,GALVANIZED" file)
         (foreach item flist (setq strdetail (lst22222str item ",")) (write-line strdetail file))
         (close file)
  )
  (progn
;;;   (alert (strcat  adfilename "file not found"))
         (print (strcat adfilename "file not found"))
         (princ)
  )
 )
)
;_
(defun summaryfileNew ()
 (setq flist nil)
 (foreach item sumlst
  (if flist
   (progn
    (setq n 0)
    (setq fbool nil)
    (setq fn nil)
    (foreach lst flist
     (if (and (eq (nth 0 lst) (nth 0 item)) (= (nth 2 lst) (nth 2 item)))
      (progn (setq fbool t) (setq fn n))
     )
     (setq n (+ n 1))
    )
    (if fbool
     (progn (setq newitem (subst (+ 1 (nth 3 (nth fn flist))) (nth 3 (nth fn flist)) (nth fn flist)))
            (setq flist (subst newitem (nth fn flist) flist))
     )
     (setq flist (cons (list (nth 0 item) (nth 1 item) (nth 2 item) 1 0 (nth 3 item)) flist))
    )
   )
   (setq
    flist (cons (list (nth 0 item) (nth 1 item) (nth 2 item) 1 0 (nth 3 item) (nth 4 item)) flist)
   )
  )
 )
 (setq n 0)
 (repeat (length flist)
  (setq item (nth n flist))             ;(setq newitem(subst (+ 1 (nth 3 (nth fn  flist))) (nth 3(nth fn  flist)) (nth fn  flist)))
  (setq newitem (subst (* (nth 2 (nth n flist)) (nth 3 (nth n flist)))
                       (nth 4 (nth n flist))
                       (nth n flist)
                )
  )
  (setq flist (subst newitem item flist))
  (setq n (+ n 1))
 )
;;; (setq n 0)
;;; (repeat (length flist)
;;;  (setq item (nth n flist))
;;;  (setq newitem (subst (* (/ (nth 4 (nth n flist)) 1000) (nth 5 (nth n flist)))
;;;                       (nth 5 (nth n flist))
;;;                       (nth n flist)
;;;                )
;;;  )
;;;  (setq flist (subst newitem item flist))
;;;  (setq n (+ n 1))
;;; )
 (write2csvNew)
)
;_
(defun summaryfile ()
 (setq flist nil)
 (foreach item sumlst
  (if flist
   (progn
    (setq n 0)
    (setq fbool nil)
    (setq fn nil)
    (foreach lst flist
     (if (and (eq (nth 0 lst) (nth 0 item)) (= (nth 2 lst) (nth 2 item)))
      (progn (setq fbool t) (setq fn n))
     )
     (setq n (+ n 1))
    )
    (if fbool
     (progn (setq newitem (subst (+ 1 (nth 3 (nth fn flist))) (nth 3 (nth fn flist)) (nth fn flist)))
            (setq flist (subst newitem (nth fn flist) flist))
     )
     (setq flist (cons (list (nth 0 item) (nth 1 item) (nth 2 item) 1 0 (nth 3 item)) flist))
    )
   )
   (setq
    flist (cons (list (nth 0 item) (nth 1 item) (nth 2 item) 1 0 (nth 3 item) (nth 4 item)) flist)
   )
  )
 )
 (setq n 0)
 (repeat (length flist)
  (setq item (nth n flist))             ;(setq newitem(subst (+ 1 (nth 3 (nth fn  flist))) (nth 3(nth fn  flist)) (nth fn  flist)))
  (setq newitem (subst (* (nth 2 (nth n flist)) (nth 3 (nth n flist)))
                       (nth 4 (nth n flist))
                       (nth n flist)
                )
  )
  (setq flist (subst newitem item flist))
  (setq n (+ n 1))
 )
 (setq n 0)
 (repeat (length flist)
  (setq item (nth n flist))
  (setq newitem (subst (* (/ (nth 4 (nth n flist)) 1000) (nth 5 (nth n flist)))
                       (nth 5 (nth n flist))
                       (nth n flist)
                )
  )
  (setq flist (subst newitem item flist))
  (setq n (+ n 1))
 )
 (write2csv)
)

 ;_
(defun summaryfileOnly ()
 (setq flist nil)
 (foreach item sumlst
  (if flist
   (progn
    (setq n 0)
    (setq fbool nil)
    (setq fn nil)
    (foreach lst flist
     (if (and (eq (nth 0 lst) (nth 0 item)) (= (nth 2 lst) (nth 2 item)))
      (progn (setq fbool t) (setq fn n))
     )
     (setq n (+ n 1))
    )
    (if fbool
     (progn (setq newitem (subst (+ 1 (nth 3 (nth fn flist))) (nth 3 (nth fn flist)) (nth fn flist)))
            (setq flist (subst newitem (nth fn flist) flist))
     )
     (setq flist (cons (list (nth 0 item) (nth 1 item) (nth 2 item) 1 0 (nth 3 item)) flist))
    )
   )
   (setq
    flist (cons (list (nth 0 item) (nth 1 item) (nth 2 item) 1 0 (nth 3 item) (nth 4 item)) flist)
   )
  )
 )
 (setq n 0)
 (repeat (length flist)
  (setq item (nth n flist))             ;(setq newitem(subst (+ 1 (nth 3 (nth fn  flist))) (nth 3(nth fn  flist)) (nth fn  flist)))
  (setq newitem (subst (* (nth 2 (nth n flist)) (nth 3 (nth n flist)))
                       (nth 4 (nth n flist))
                       (nth n flist)
                )
  )
  (setq flist (subst newitem item flist))
  (setq n (+ n 1))
 )
 (setq n 0)
 (repeat (length flist)
  (setq item (nth n flist))
  (setq newitem (subst (* (/ (nth 4 (nth n flist)) 1000) (nth 5 (nth n flist)))
                       (nth 5 (nth n flist))
                       (nth n flist)
                )
  )
  (setq flist (subst newitem item flist))
  (setq n (+ n 1))
 )
 (writeSummary2csv)
)
 ;_
(defun C:MTONew ()                         ;addlength ()
 (defun *error* (msg) (vl-cmdf "UNDO" "b") (princ msg))
 (vl-cmdf "UNDO" "m")
 (setvar "cmdecho" 0)
;;; (setq tot_len 0)
 (vl-load-com)
 (chkpwd)
 (if pwd
  (progn
 (setq smbool nil)
 (prompt "\nSelect all objects to count: ")
 (setq ss (ssget))
 (setq sobj (ssname ss 0))
 (setq sdata (entget sobj))
 (setq sla (cdr (assoc 8 sdata)))
;;; (setq la(getvar "clayer"))
;;; (command "layer" "m" "calc" "")
 (setq n 0)
 (setq detailsbool nil)
 (setq rbool nil)
 (setq writebool nil)
 (setq laylist nil)
 (while (< n (sslength ss))
  (setq nobj (ssname ss n))
  (setq objname (cdr (assoc 0 (entget nobj))))
  (setq objlay (cdr (assoc 8 (entget nobj))))
  (if (or (= objname "LINE") (= objname "ARC") (= objname "POLYLINE") (= objname "LWPOLYLINE"))
   (progn (setq obj (vlax-ename->vla-object nobj))
          (if laylist
           (progn (setq lbool nil)
                  (foreach item laylist
                   (if (wcmatch item objlay)
                    (setq lbool t)
                   )
                  )
                  (if (= lbool nil)
                   (setq laylist (cons objlay laylist))
                  )
           )
           (setq laylist (cons objlay laylist))
          )
   )
  )
  (setq n (+ n 1))
 )
;;; (xplodepolylines)
 (setq tempset (ssadd))
 (duplicates)
 (foreach layitem laylist
  (setq lset (ssadd))
  (setq lcount 0)
  (setq tot_len 0)
  (setq len_lst nil)
  (repeat (sslength tempset)
   (setq lset (ssadd (ssname tempset lcount) lset))
   (setq lcount (+ lcount 1))
  )
  (setq n (- (sslength lset) 1))
  (while (> (sslength lset) 0)
   (setq en (ssname lset n))
   (setq ed (entget en))
   (setq elay (cdr (assoc 8 ed)))
   (setq e_type (cdr (assoc '0 ed)))
   (cond ((= e_type "LINE") (add_lines))
         ((= e_type "ARC") (add_arcs))
         ((= e_type "POLYLINE") (add_poly))
         ((= e_type "LWPOLYLINE") (add_poly))
         ((and (/= e_type "LINE") (/= e_type "ARC") (/= e_type "POLYLINE") (/= e_type "LWPOLYLINE"))
          (ssdel en lset)
         )
   )
   (setq n (- n 1))
  )
  (updatefileNew)
 )
;;; (princ)
 (setvar "cmdecho" 1)
 (print "Success")
 (princ)
 )
  )
)
;_
(defun C:MTO ()                         ;addlength ()
 (defun *error* (msg) (vl-cmdf "UNDO" "b") (princ msg))
 (vl-cmdf "UNDO" "m")
 (setvar "cmdecho" 0)
;;; (setq tot_len 0)
 (vl-load-com)
 (chkpwd)
 (if pwd
  (progn
 (setq smbool nil)
 (prompt "\nSelect all objects to count: ")
 (setq ss (ssget))
 (setq sobj (ssname ss 0))
 (setq sdata (entget sobj))
 (setq sla (cdr (assoc 8 sdata)))
;;; (setq la(getvar "clayer"))
;;; (command "layer" "m" "calc" "")
 (setq n 0)
 (setq detailsbool nil)
 (setq rbool nil)
 (setq writebool nil)
 (setq laylist nil)
 (while (< n (sslength ss))
  (setq nobj (ssname ss n))
  (setq objname (cdr (assoc 0 (entget nobj))))
  (setq objlay (cdr (assoc 8 (entget nobj))))
  (if (or (= objname "LINE") (= objname "ARC") (= objname "POLYLINE") (= objname "LWPOLYLINE"))
   (progn (setq obj (vlax-ename->vla-object nobj))
          (if laylist
           (progn (setq lbool nil)
                  (foreach item laylist
                   (if (wcmatch item objlay)
                    (setq lbool t)
                   )
                  )
                  (if (= lbool nil)
                   (setq laylist (cons objlay laylist))
                  )
           )
           (setq laylist (cons objlay laylist))
          )
   )
  )
  (setq n (+ n 1))
 )
;;; (xplodepolylines)
 (setq tempset (ssadd))
 (duplicates)
 (foreach layitem laylist
  (setq lset (ssadd))
  (setq lcount 0)
  (setq tot_len 0)
  (setq len_lst nil)
  (repeat (sslength tempset)
   (setq lset (ssadd (ssname tempset lcount) lset))
   (setq lcount (+ lcount 1))
  )
  (setq n (- (sslength lset) 1))
  (while (> (sslength lset) 0)
   (setq en (ssname lset n))
   (setq ed (entget en))
   (setq elay (cdr (assoc 8 ed)))
   (setq e_type (cdr (assoc '0 ed)))
   (cond ((= e_type "LINE") (add_lines))
         ((= e_type "ARC") (add_arcs))
         ((= e_type "POLYLINE") (add_poly))
         ((= e_type "LWPOLYLINE") (add_poly))
         ((and (/= e_type "LINE") (/= e_type "ARC") (/= e_type "POLYLINE") (/= e_type "LWPOLYLINE"))
          (ssdel en lset)
         )
   )
   (setq n (- n 1))
  )
  (updatefile)
 )
;;; (princ)
 (setvar "cmdecho" 1)
 (print "Success")
 (princ)
 )
  )
)
 ;_
(defun RoundUp (n)
 (if (or (minusp n) (zerop (rem n 25)))
  (fix n)
  (fix (+ 25 (- n (rem n 25))))
 )
)
;_
(defun RoundUpold (n)
 (if (or (minusp n) (zerop (rem n 50)))
  (fix n)
  (fix (+ 50 (- n (rem n 50))))
 )
)
;_
(defun updatefile ()
 (setq dwgpath (getvar "DWGPREFIX"))
 (setq adfilename (strcat dwgpath "MATERIAL-TAKEOFF.csv"))
 (setq file (findfile adfilename))
 (if file
  (progn
   (setq fcount 0)
   (setq fs (open file "r"))
   (setq data nil)
   (setq details nil)
   (while (and (setq ln (read-line fs)) (/= "EOF" ln) (/= "" ln))
    (setq fcount (+ fcount 1))
    (setq data (cons (str2lst ln "," nil) data))
   )
   (close fs)
   (setq data (reverse data))
   (filechk)
   (setq foundbool nil)
   (if data
    (progn
     (setq n 0) 
     (foreach item data
      (if(/= n 0)
       (progn
      (setq layername   (car item)
            profilename (cadr item)
            totallength (caddr item)
;;;                col         (atoi (last item))
            col         (nth 5 item)
      )
      (setq tot_wt 0)
;;;      (setq wt (rtos (getWt profilename)))
      (setq wt (getWt profilename))
;;;      (if (or (= wt "") (= wt nil))
;;;         (progn (alert (strcat "missing data  wt/m  for profile:" profilename ".Update & rerun ")) (exit))
;;;         ;(setq wt (rtos wt))
;;;        )
      (if (/= wt nil)
;;;          (setq tot_wt(* (atof wt) tot_len))
       (setq tot_wt (* (atof wt) (/ tot_len 1000)))
       (progn
        (if
         (not
          (or (wcmatch (strcase profilename) "PROFILE*") (wcmatch (strcase profilename) "UNKNOWN*"))
         )
;;;           (alert (strcat "missing  detail for profile:" profilename))
         (progn (print (strcat "missing  detail for profile:" profilename)) (princ))
        )
       )
      )
      (if (wcmatch layername layitem)
       (progn (setq details (cons (SubstOnce (rtos tot_len 2 2) (nth 2 item) item) details))
;;;                    (setq details (cons (SubstOnce (mapcar 'vl-princ-to-string len_lst) (nth 2 item) item) details))
              (setq
               details (SubstOnce (SubstOnce (rtos tot_wt 2 2) (nth 3 (nth 0 details)) (nth 0 details))
                                  (nth 0 details)
                                  details
                       )
              )
;;;                    (setq details(append details (mapcar 'vl-princ-to-string len_lst)))
              (setq foundbool t)
       )
       (setq details (cons item details))
      )
      )
     )
      (setq n(+ n 1))
     )
;;;         (setq details (reverse detailS))
    )
    (progn (setq details (cons (list layitem "UNKNOWN" (rtos tot_len 2 2) "" "" "1") details))
;;;           (setq details (cons(append(list layitem "UNKNOWN"  (rtos tot_len 2 2) "" "" "1")(mapcar 'vl-princ-to-string len_lst)) details))
    )
   )
   (if (= foundbool nil)
    (progn (setq details (cons (list layitem "UNKNOWN" (rtos tot_len 2 2) "" "" "1") details))
           (setq data (append data (list (list layitem "UNKNOWN" (rtos tot_len 2 2) "" "" "1"))))
;;;     (setq details (cons(append(list layitem "UNKNOWN"  (rtos tot_len 2 2) "" "" "1")(mapcar 'vl-princ-to-string len_lst)) details))
;;;     (setq data(append data (list(append(list layitem "UNKNOWN"  (rtos tot_len 2 2) "" "" "1")(mapcar 'vl-princ-to-string len_lst)))))     
    )
   )
   (setq details (reverse detailS))
   (writecsv)
  )
  (progn
;;;   (alert (strcat  adfilename "file not found"))
         (print (strcat adfilename "file not found"))
         (princ)
  )
 )
)
 ;_
(defun updatefileNew ()
 (setq dwgpath (getvar "DWGPREFIX"))
 (setq adfilename (strcat dwgpath "MATERIAL-TAKEOFF.csv"))
 (setq file (findfile adfilename))
 (if file
  (progn
   (setq fcount 0)
   (setq fs (open file "r"))
   (setq data nil)
   (setq details nil)
   (while (and (setq ln (read-line fs)) (/= "EOF" ln) (/= "" ln))
    (setq fcount (+ fcount 1))
    (setq data (cons (str2lst ln "," nil) data))
   )
   (close fs)
   (setq data (reverse data))
   (filechk)
   (setq foundbool nil)
   (if data
    (progn
     (setq n 0) 
     (foreach item data
      (if(/= n 0)
       (progn
      (setq layername   (car item)
            profilename (cadr item)
            totallength (caddr item)
;;;                col         (atoi (last item))
            col         (nth 5 item)
      )
      (setq tot_wt 0)
;;;      (setq wt (rtos (getWt profilename)))
      ;(setq wt (getWt profilename))
;;;      (if (or (= wt "") (= wt nil))
;;;         (progn (alert (strcat "missing data  wt/m  for profile:" profilename ".Update & rerun ")) (exit))
;;;         ;(setq wt (rtos wt))
;;;        )
      (setq wt " ")
;;;      (if (/= wt nil)
;;;;;;          (setq tot_wt(* (atof wt) tot_len))
;;;       (setq tot_wt (* (atof wt) (/ tot_len 1000)))
;;;       (progn
;;;        (if
;;;         (not
;;;          (or (wcmatch (strcase profilename) "PROFILE*") (wcmatch (strcase profilename) "UNKNOWN*"))
;;;         )
;;;;;;           (alert (strcat "missing  detail for profile:" profilename))
;;;         (progn (print (strcat "missing  detail for profile:" profilename)) (princ))
;;;        )
;;;       )
;;;      )
      (setq tot_wt " ")
      (if (wcmatch layername layitem)
       (progn (setq details (cons (SubstOnce (rtos tot_len 2 2) (nth 2 item) item) details))
;;;                    (setq details (cons (SubstOnce (mapcar 'vl-princ-to-string len_lst) (nth 2 item) item) details))
              (setq
               details (SubstOnce (SubstOnce tot_wt  (nth 3 (nth 0 details)) (nth 0 details))
                                  (nth 0 details)
                                  details
                       )
              )
;;;                    (setq details(append details (mapcar 'vl-princ-to-string len_lst)))
              (setq foundbool t)
       )
       (setq details (cons item details))
      )
      )
     )
      (setq n(+ n 1))
     )
;;;         (setq details (reverse detailS))
    )
    (progn (setq details (cons (list layitem "UNKNOWN" (rtos tot_len 2 2) "" "" "1") details))
;;;           (setq details (cons(append(list layitem "UNKNOWN"  (rtos tot_len 2 2) "" "" "1")(mapcar 'vl-princ-to-string len_lst)) details))
    )
   )
   (if (= foundbool nil)
    (progn (setq details (cons (list layitem "UNKNOWN" (rtos tot_len 2 2) "" "" "1") details))
           (setq data (append data (list (list layitem "UNKNOWN" (rtos tot_len 2 2) "" "" "1"))))
;;;     (setq details (cons(append(list layitem "UNKNOWN"  (rtos tot_len 2 2) "" "" "1")(mapcar 'vl-princ-to-string len_lst)) details))
;;;     (setq data(append data (list(append(list layitem "UNKNOWN"  (rtos tot_len 2 2) "" "" "1")(mapcar 'vl-princ-to-string len_lst)))))     
    )
   )
   (setq details (reverse detailS))
   (writecsv)
  )
  (progn
;;;   (alert (strcat  adfilename "file not found"))
         (print (strcat adfilename "file not found"))
         (princ)
  )
 )
)
 ;_
(defun getYesNo ()
 (setq result nil)
 (setq yes (getstring "Do you want to overwrite? Enter Y for Yes or N or No:"))
 (if (wcmatch (strcase yes) "Y")
  (setq result t)
 )
 (if (not (or (wcmatch (strcase yes) "Y") (wcmatch (strcase yes) "N")))
  (progn (alert "Invalid Output.Exiting...") (exit))
 )
)
 ;_
(defun SubstOnce (a b l)
 (mapcar '(lambda (x)
           (if (equal b x)
            (setq x a
                  a nil
                  b nil
            )
           )
           x
          )
         l
 )
)
 ;_
(defun filechk ()
 (setq dcount 0)
 (foreach item data
  (setq layername   (car item)
        profilename (cadr item)
;;;        col        (atoi(last item))
        col         (nth 5 item)
  )
;;;  (setq ps (vl-string-search "-" layername))
;;;  (setq layer (substr layername 1 ps))
;;;  (setq lname (strcat sname layer))
  (if (> dcount 0)
   (if (or (= profilename "") (= layername "") (= col 0))
    (progn
;;;   (cond 
;;;                ((= col 0) (alert "color missing , check csv file"))
;;;                ((= layername "") (alert "Layer name missing , check csv file"))
;;;                ((= profilename "") (alert "Profilename missing , check csv file"))
;;;          )
           (cond ((= col 0) (print "color missing , check csv file") (princ))
                 ((= layername "") (print "Layer name missing , check csv file") (princ))
                 ((= profilename "") (print "Profilename missing , check csv file") (princ))
           )
           (exit)
    )
   )
  )
  (setq dcount (+ dcount 1))
 )
)
 ;_
(defun getwt (pname / val)
 (setq wfilename (strcat "C:\\STEEL-SECTIONS\\" "AUSTRALIAN-SECTIONS.csv")) ;(setq file filename )
 (setq file (findfile wfilename))
 (if file
  (progn (setq fcount 0)
;;;    (close fs)
         (setq fs (open file "r"))
         (setq wdata nil)
         (while (and (setq ln (read-line fs)) (/= "EOF" ln))
          (setq fcount (+ fcount 1))
          (if (> fcount 1)
           (setq wdata (cons (str2lst ln "," nil) wdata))
          )
         )
         (close fs)
         (setq wdata (reverse wdata))
         (setq val nil)
         (foreach item wdata
          (setq profile (car item)
                wtm     (cadr item)
          )
          (if (wcmatch pname profile)
           (setq val wtm)
          )
         )
  )
;;;  (alert (strcat wfilename "file not found"))
  (progn (print (strcat wfilename "file not found")) (princ))
 )
 val
)
 ;_
(defun str2lst (strg delim trim / templist pos)
 (if trim
  (setq strg (vl-string-trim delim strg))
 )
 (setq templist (list))
 (while (setq pos (vl-string-search delim strg))
  (setq templist (cons (substr strg 1 pos) templist)
        strg     (substr strg (+ 2 pos))
  )
 )
 (reverse (cons strg templist))
)
 ;_
(defun writecsv ()
 (setq file (open adfilename "w"))
 (foreach item details (setq strdetail (lst2str item ",")) (write-line strdetail file))
 (close file)
)
;_
(defun lst22222strNew (lst del / str)
 (setq str (car lst))
 (setq sbool nil)
 (setq cs 0)
 (foreach itm (cdr lst)
  (if(/= itm " ")
   (progn
    
  (if (= sbool nil)
   (progn (setq str (strcat str del itm)) (setq sbool t))
   (progn (setq str (strcat str del (rtos itm)))
          (if (= cs 4)
           (setq sbool nil)
          )
   )
  )
  )
   )
  (setq cs (+ cs 1))
 )
 str
)
 ;_
(defun lst22222str (lst del / str)
 (setq str (car lst))
 (setq sbool nil)
 (setq cs 0)
 (foreach itm (cdr lst)
  (if (= sbool nil)
   (progn (setq str (strcat str del itm)) (setq sbool t))
   (progn (setq str (strcat str del (rtos itm)))
          (if (= cs 4)
           (setq sbool nil)
          )
   )
  )
  (setq cs (+ cs 1))
 )
 str
)
 ;_
(defun lst2222strNew (lst del / str)
 (setq str (car lst))
 (setq sbool nil)
 (setq cs 0)
 (foreach itm (cdr lst)
  (if (/= itm " ")
   (progn
  (if (= sbool nil)
   (progn (setq str (strcat str del itm)) (setq sbool t))
   (progn (setq str (strcat str del (rtos itm)))
          (if (= cs 2)
           (setq sbool nil)
          )
   )
  )
  )
   )
  (setq cs (+ cs 1))
 )
 str
)
;_
(defun lst2222str (lst del / str)
 (setq str (car lst))
 (setq sbool nil)
 (setq cs 0)
 (foreach itm (cdr lst)
  (if (= sbool nil)
   (progn (setq str (strcat str del itm)) (setq sbool t))
   (progn (setq str (strcat str del (rtos itm)))
          (if (= cs 2)
           (setq sbool nil)
          )
   )
  )
  (setq cs (+ cs 1))
 )
 str
)
 ;_
(defun lst222str (lst del / str)
 (setq str (car lst))                   ; (setq str "")
                                        ;(foreach itm lst (setq str (strcat str (car itm) del (cadr itm))))
 (setq sbool nil)
 (foreach itm (cdr lst)
  (if (= sbool nil)
   (progn (setq str (strcat str del itm)) (setq sbool t))
   (progn (setq str (strcat str del (rtos itm))) (setq sbool nil))
  )
 )
 str
)
 ;_

(defun lst22str (lst del / str)
 (setq str (car lst))                   ; (setq str "")
                                        ;(foreach itm lst (setq str (strcat str (car itm) del (cadr itm))))
 (foreach itm (cdr lst) (setq str (strcat str del (car itm) del (rtos (cadr itm)))))
 str
)
 ;_
(defun lst2str (lst del / str)
 (setq str (car lst))
 (foreach itm (cdr lst) (setq str (strcat str del itm)))
 str
)
 ;_

(defun add_lines ()
 (setq pt1 (cdr (assoc '10 ed)))
 (setq pt2 (cdr (assoc '11 ed)))
 (if (/= (caddr pt1) 0)
  (setq pt1 (list (car pt1) (cadr pt1) 0))
 )
 (if (/= (cadr pt2) 0)
  (setq pt2 (list (car pt2) (cadr pt2) 0))
 )
 (setq line_len (distance pt1 pt2))
 (if (wcmatch elay layitem)
  (progn (if (> line_len 10)
          (progn (createtext)
                 (setq tot_len (+ tot_len line_len))
                 (setq len_lst (cons (roundup line_len) len_lst))
                 (setq sumlst (cons (list elay pr (roundup line_len) wt gvn) sumlst))
          )
         )
  )
 )
 (ssdel en lset)
)
 ;_
(defun createtext ()
 (setq midpt (list (/ (+ (car pt1) (car pt2)) 2) (/ (+ (cadr pt1) (cadr pt2)) 2) 0))
 (setq ang (/ (* (angle pt1 pt2) 180) pi))
 (setq tt nil)
 (setq wp1 (list (+ (car pt1) 5) (+ (cadr pt1) 5))
       wp2 (list (- (car pt2) 5) (- (cadr pt2) 5))
 )
 (setq tt (ssget "C" wp1 wp2 (list (cons 0 "TEXT") (cons 8 elay))))
 (if tt
  (vl-cmdf "erase" tt "")
 )
 (vl-cmdf "text" "justify" "center" midpt 400 ang elay)
;;;  (setq txt(entlast))
 (vla-put-layer (vlax-ename->vla-object (entlast)) elay)
)
 ;_

(defun add_arcs ()
 (setq CEN    (cdr (assoc '10 Ed))
       RAD    (cdr (assoc '40 Ed))
       DIA    (* RAD 2.0)
       CIRCUM (* (* RAD pi) 2.0)
       S_ANG  (cdr (assoc '50 Ed))
       E_ANG  (cdr (assoc '51 Ed))
 )
 (if (< E_ANG S_ANG)
  (setq E_ANG (+ E_ANG (* pi 2.0)))
 )
 (setq N_ANG     (- E_ANG S_ANG)
       N_ANG_1   (* (/ N_ANG pi) 180.0)
       PART_CIRC (/ N_ANG_1 360.0)
       A_LEN     (* PART_CIRC CIRCUM)
 )
 (if (wcmatch elay layitem)
  (progn (if (> a_len 10)
          (progn (setq tot_len (+ tot_len a_len))
                 (setq sumlst (cons (list elay pr (roundup a_len) wt gvn) sumlst))
          )
         )
  )
 )
 (prin1)
 (ssdel EN lset)
)
 ;_

(defun add_poly ()
 (command "area" "e" en)
 (if (wcmatch elay layitem)
  (progn (if (> (getvar "perimeter") 10)
          (progn (setq tot_len (+ tot_len (getvar "perimeter")))
                 (setq sumlst (cons (list elay pr (roundup (getvar "perimeter")) wt gvn) sumlst))
          )
         )
  )
 )
 (ssdel en lset)
)
 ;_
(defun duplicates ()
;;;(setq ss (ssget "X" '((8 . "calc"))))
 (if (/= ss nil)
  (progn
   (setq objs ss)
   (setq LineColl nil
         EntColl nil
   )
   (setq DupSS (ssadd))
   (repeat (setq i (sslength objs))
    (setq entN (ssname objs (setq i (1- i))))
    (setq ent (entget entN))
    (setq etype (cdr (assoc '0 ent)))
    (cond ((or (= etype "LINE") (= etype "LINE") (= etype "ARC"))
           (foreach itm '(-1 5 330 62) (setq ent (vl-remove (assoc (eval itm) ent) ent)))
           (setq LineColl (cons ent LineColl)
                 EntColl  (cons (list ent entN) Entcoll)
           )
          )
          ((wcmatch etype "*POLYLINE") (setq dupss (ssadd entN dupss)))
          ((and (/= etype "LINE") (/= etype "ARC") (/= etype "POLYLINE") (/= etype "LWPOLYLINE"))
           (ssdel entN ss)
          )
    )
   )
   (setq b   nil
         lnt (length LineColl)
   )
   (while (setq a (car LineColl))
    (setq b        (cons a b)
          LineColl (vl-remove a (cdr LineColl))
    )
    (if (/= lnt (length LineColl))
     (setq Dupss (ssadd (cadr (setq LstR (assoc a entcoll))) DupSS))
     (setq lnt (length LineColl))
    )
   )
   (if (> (sslength dupss) 0)
    (setq tempset dupss)
    (setq tempset ss)
   )
  )
 )
)
 ;_
(defun xplodepolylines ()
 (setq ss (ssget "X" '((8 . "calc"))))
 (if (/= ss nil)
  (progn (setq a (- (sslength ss) 1))
         (while (>= a 0)
          (setq tobj (ssname ss a)
                data (entget tobj)
                ty   (cdr (assoc '0 data))
          )
          (if (or (= ty "POLYLINE") (= ty "LWPOLYLINE"))
           (command "explode" tobj)
          )
          (setq a (- a 1))
         )
  )
 )
)

 ;_
(defun ADDlspYesNo (message1 message2 main)
;;; (setq filename (strcat (getvar "roamablerootprefix") "ADDmsgbox.dcl"))
 (setq filename (strcat (getvar "dwgprefix") "ADDmsgbox.dcl"))
 (writedcl filename)
 (setq file (findfile filename))
 (setq dcl_id (load_dialog file))
 (if (not (new_dialog "ADDlspYesNo" dcl_id))
  (exit)
 )
 (set_tile "message1" message1)
 (set_tile "message2" message2)
 (set_tile "main" main)
 (action_tile "no" "(done_dialog)
     (setq result nil)")
 (action_tile "yes" "(done_dialog)
     (setq result T)")
 (start_dialog)
 (unload_dialog dcl_id)
 (princ)
)
 ;_
(defun WriteDCL (fname / ofile)
;;; (if (not (findfile fname))
 (if (setq ofile (open fname "w"))
  (progn (foreach str '("ADDlspYesNo : dialog {" "key = \"main\";" ": column {" ": text {"
                        "key = \"message1\";" "}" ": text {
	key = \"message2\";" "}" "}" ": row {" ": spacer { width = 1; }" ": button {"
                        "label = \"Yes\";" "key = \"yes\";" "width = 12;" "fixed_width = true;"
                        "mnemonic = \"Y\";" "is_default = true;" "}" ": button {" "label = \"No\";"
                        "key = \"no\";" "width = 12;" "fixed_width = true;" "mnemonic = \"N\";"
                        "is_cancel = true;" "}" ": spacer { width = 1;}" "}" "}"
                       )
          (write-line str ofile)
         )
         (setq ofile (close ofile))
         (while (not (findfile fname)))
         t
  )                                     ; File written successfully
  nil
 )                                      ; Filepath not Found
;;;  t
;;; )
)
;|«Visual LISP© Format Options»
(100 1 40 2 nil "end of " 100 9 1 0 1 nil nil nil T)
;*** DO NOT add text below the comment! ***|;
